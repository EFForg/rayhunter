-- This file was generated by the Objective Systems ASN1C Compiler
-- (http://www.obj-sys.com).  Version: 7.7.2, Date: 13-Oct-2023.

EUTRA-InterNodeDefinitions DEFINITIONS AUTOMATIC TAGS ::= BEGIN

IMPORTS

AntennaInfoCommon, AntennaInfoDedicated-v10i0, ARFCN-ValueEUTRA, 
   ARFCN-ValueEUTRA-v9e0, ARFCN-ValueEUTRA-r9, CellIdentity, C-RNTI, 
   DAPS-PowerCoordinationInfo-r16, DL-DCCH-Message, DRB-Identity, 
   DRB-ToReleaseList, DRB-ToReleaseList-r15, FreqBandIndicator-r11, 
   InDeviceCoexIndication-r11, LWA-Config-r13, MasterInformationBlock, maxBands
   , maxFreq, maxDRB, maxDRBExt-r15, maxDRB-r15, maxSCell-r10, maxSCell-r13, 
   maxServCell-r10, maxServCell-r13, MBMSInterestIndication-r11, MeasConfig, 
   MeasGapConfig, MeasGapConfigPerCC-List-r14, MeasResultForRSSI-r13, 
   MeasResultListWLAN-r13, OtherConfig-r9, PhysCellId, P-Max, 
   PowerCoordinationInfo-r12, SidelinkUEInformation-r12, SL-CommConfig-r12, 
   SL-DiscConfig-r12, SubframeAssignment-r15, RadioResourceConfigDedicated, 
   RadioResourceConfigDedicated-v13c0, RadioResourceConfigDedicated-v1370, 
   RAN-NotificationAreaInfo-r15, RCLWI-Configuration-r13, RSRP-Range, 
   RSRQ-Range, RSRQ-Range-v1250, RS-SINR-Range-r13, SCellToAddModList-r10, 
   SCellToAddModList-v13c0, SCellToAddModListExt-r13, 
   SCellToAddModListExt-v13c0, SCG-ConfigPartSCG-r12, SCG-ConfigPartSCG-v12f0, 
   SCG-ConfigPartSCG-v13c0, SecurityAlgorithmConfig, SCellIndex-r10, 
   SCellIndex-r13, SCellToReleaseList-r10, SCellToReleaseListExt-r13, 
   ServCellIndex-r10, ServCellIndex-r13, ShortMAC-I, 
   MeasResultServFreqListNR-r15, MeasResultSSTD-r13, SL-V2X-ConfigDedicated-r14
   , SystemInformationBlockType1, SystemInformationBlockType1-v890-IEs, 
   SystemInformationBlockType2, TDM-PatternConfig-r15, 
   UEAssistanceInformation-r11, UECapabilityInformation, 
   UE-CapabilityRAT-ContainerList, UE-RadioPagingInfo-r12, 
   WLANConnectionStatusReport-r13, WLAN-OffloadConfig-r12
FROM EUTRA-RRC-Definitions ;

-- Productions

Key-eNodeB-Star ::= BIT STRING  (SIZE (256))

HandoverCommand-r8-IEs ::= SEQUENCE {
   handoverCommandMessage [0] OCTET STRING (CONTAINING DL-DCCH-Message),
   nonCriticalExtension [1] SEQUENCE {

   } OPTIONAL
}

HandoverCommand ::= SEQUENCE {
   criticalExtensions [0] EXPLICIT CHOICE {
      c1 [0] EXPLICIT CHOICE {
         handoverCommand-r8 [0] HandoverCommand-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

SCG-Config-v12i0b-IEs ::= SEQUENCE {
   scg-RadioConfig-v12i0 [0] SCG-ConfigPartSCG-v12f0 OPTIONAL,
   nonCriticalExtension [1] SEQUENCE {

   } OPTIONAL
}

SCG-Config-v13c0-IEs ::= SEQUENCE {
   scg-RadioConfig-v13c0 [0] SCG-ConfigPartSCG-v13c0 OPTIONAL,
--Following field is only for late non-critical extensions from REL-13 onwards
   nonCriticalExtension [1] SEQUENCE {

   } OPTIONAL
}

SCG-Config-v12i0a-IEs ::= SEQUENCE {
--Following field is only for late non-critical extensions from REL-12
   lateNonCriticalExtension [0] OCTET STRING (CONTAINING SCG-Config-v12i0b-IEs)
       OPTIONAL,
   nonCriticalExtension [1] SCG-Config-v13c0-IEs OPTIONAL
}

SCG-Config-r12-IEs ::= SEQUENCE {
   scg-RadioConfig-r12 [0] SCG-ConfigPartSCG-r12 OPTIONAL,
   nonCriticalExtension [1] SCG-Config-v12i0a-IEs OPTIONAL
}

SCG-Config-r12 ::= SEQUENCE {
   criticalExtensions [0] EXPLICIT CHOICE {
      c1 [0] EXPLICIT CHOICE {
         scg-Config-r12 [0] SCG-Config-r12-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

AS-ConfigNR-r15 ::= SEQUENCE {
   sourceRB-ConfigNR-r15 [0] OCTET STRING OPTIONAL,
   sourceRB-ConfigSN-NR-r15 [1] OCTET STRING OPTIONAL,
   sourceOtherConfigSN-NR-r15 [2] OCTET STRING OPTIONAL
}

AS-Config-v1550 ::= SEQUENCE {
   tdm-PatternConfig-r15 [0] SEQUENCE {
      subframeAssignment-r15 [0] SubframeAssignment-r15,
      harq-Offset-r15 [1] INTEGER (0..9)
   } OPTIONAL,
   p-MaxEUTRA-r15 [1] P-Max OPTIONAL
}

AS-ConfigNR-v1570 ::= SEQUENCE {
   sourceSCG-ConfiguredNR-r15 [0] ENUMERATED { true(0) }
}

AS-ConfigNR-v1620 ::= SEQUENCE {
   tdm-PatternConfig2-r16 [0] EXPLICIT TDM-PatternConfig-r15
}

AS-Config ::= SEQUENCE {
   sourceMeasConfig [0] MeasConfig,
   sourceRadioResourceConfig [1] RadioResourceConfigDedicated,
   sourceSecurityAlgorithmConfig [2] SecurityAlgorithmConfig,
   sourceUE-Identity [3] C-RNTI,
   sourceMasterInformationBlock [4] MasterInformationBlock,
   sourceSystemInformationBlockType1 [5] SystemInformationBlockType1 (
      WITH COMPONENTS {..., nonCriticalExtension ABSENT}),
   sourceSystemInformationBlockType2 [6] SystemInformationBlockType2,
   antennaInfoCommon [7] AntennaInfoCommon,
   sourceDl-CarrierFreq [8] ARFCN-ValueEUTRA,
   ...,
   [[
      sourceSystemInformationBlockType1Ext [9] OCTET STRING (CONTAINING 
         SystemInformationBlockType1-v890-IEs) OPTIONAL,
      sourceOtherConfig-r9 [10] OtherConfig-r9
   ]],
   [[
      sourceSCellConfigList-r10 [11] SCellToAddModList-r10 OPTIONAL
   ]],
   [[
      sourceConfigSCG-r12 [12] SCG-Config-r12 OPTIONAL
   ]],
   [[
      as-ConfigNR-r15 [13] AS-ConfigNR-r15 OPTIONAL
   ]],
   [[
      as-Config-v1550 [14] AS-Config-v1550 OPTIONAL
   ]],
   [[
      as-ConfigNR-v1570 [15] AS-ConfigNR-v1570 OPTIONAL
   ]],
   [[
      as-ConfigNR-v1620 [16] AS-ConfigNR-v1620 OPTIONAL
   ]]
}

CandidateCellInfo-r10 ::= SEQUENCE {
--cellIdentification
   physCellId-r10 [0] PhysCellId,
   dl-CarrierFreq-r10 [1] ARFCN-ValueEUTRA,
--available measurement results
   rsrpResult-r10 [2] RSRP-Range OPTIONAL,
   rsrqResult-r10 [3] RSRQ-Range OPTIONAL,
   ...,
   [[
      dl-CarrierFreq-v1090 [4] ARFCN-ValueEUTRA-v9e0 OPTIONAL
   ]],
   [[
      rsrqResult-v1250 [5] RSRQ-Range-v1250 OPTIONAL
   ]],
   [[
      rs-sinr-Result-r13 [6] RS-SINR-Range-r13 OPTIONAL
   ]]
}

CandidateCellInfoList-r10 ::= SEQUENCE (SIZE (1..maxFreq)) OF CandidateCellInfo-r10

RRM-Config ::= SEQUENCE {
   ue-InactiveTime [0] ENUMERATED { s1(0), s2(1), s3(2), s5(3), s7(4), s10(5), 
      s15(6), s20(7), s25(8), s30(9), s40(10), s50(11), min1(12), min1s20c(13)
      , min1s40(14), min2(15), min2s30(16), min3(17), min3s30(18), min4(19), 
      min5(20), min6(21), min7(22), min8(23), min9(24), min10(25), min12(26), 
      min14(27), min17(28), min20(29), min24(30), min28(31), min33(32), 
      min38(33), min44(34), min50(35), hr1(36), hr1min30(37), hr2(38), 
      hr2min30(39), hr3(40), hr3min30(41), hr4(42), hr5(43), hr6(44), hr8(45), 
      hr10(46), hr13(47), hr16(48), hr20(49), day1(50), day1hr12(51), day2(52)
      , day2hr12(53), day3(54), day4(55), day5(56), day7(57), day10(58), 
      day14(59), day19(60), day24(61), day30(62), dayMoreThan30(63) } OPTIONAL,
   ...,
   [[
      candidateCellInfoList-r10 [1] CandidateCellInfoList-r10 OPTIONAL
   ]],
   [[
      candidateCellInfoListNR-r15 [2] MeasResultServFreqListNR-r15 OPTIONAL
   ]]
}

AdditionalReestabInfo ::= SEQUENCE {
   cellIdentity [0] CellIdentity,
   key-eNodeB-Star [1] Key-eNodeB-Star,
   shortMAC-I [2] ShortMAC-I
}

AdditionalReestabInfoList ::= SEQUENCE (SIZE (1..maxReestabInfo)) OF AdditionalReestabInfo

ReestablishmentInfo ::= SEQUENCE {
   sourcePhysCellId [0] PhysCellId,
   targetCellShortMAC-I [1] ShortMAC-I,
   additionalReestabInfoList [2] AdditionalReestabInfoList OPTIONAL,
   ...
}

AS-Context ::= SEQUENCE {
   reestablishmentInfo [0] ReestablishmentInfo OPTIONAL -- Cond HO
}

AS-Config-v10j0 ::= SEQUENCE {
   antennaInfoDedicatedPCell-v10i0 [0] AntennaInfoDedicated-v10i0 OPTIONAL
}

AS-Config-v13c0 ::= SEQUENCE {
   radioResourceConfigDedicated-v13c01 [0] RadioResourceConfigDedicated-v1370
       OPTIONAL,
   radioResourceConfigDedicated-v13c02 [1] RadioResourceConfigDedicated-v13c0
       OPTIONAL,
   sCellToAddModList-v13c0 [2] SCellToAddModList-v13c0 OPTIONAL,
   sCellToAddModListExt-v13c0 [3] SCellToAddModListExt-v13c0 OPTIONAL
}

HandoverPreparationInformation-v13c0-IEs ::= SEQUENCE {
   as-Config-v13c0 [0] AS-Config-v13c0 OPTIONAL,
--Following field is only for late non-critical extensions from REL-13
   nonCriticalExtension [1] SEQUENCE {

   } OPTIONAL
}

HandoverPreparationInformation-v10x0-IEs ::= SEQUENCE {
--Following field is only for late non-critical extensions from REL-10 to REL-12
   lateNonCriticalExtension [0] OCTET STRING OPTIONAL,
   nonCriticalExtension [1] HandoverPreparationInformation-v13c0-IEs OPTIONAL
}

HandoverPreparationInformation-v10j0-IEs ::= SEQUENCE {
   as-Config-v10j0 [0] AS-Config-v10j0 OPTIONAL,
   nonCriticalExtension [1] HandoverPreparationInformation-v10x0-IEs OPTIONAL
}

-- Late non-critical extensions:
HandoverPreparationInformation-v9j0-IEs ::= SEQUENCE {
--Following field is only for pre REL-10 late non-critical extensions
   lateNonCriticalExtension [0] OCTET STRING OPTIONAL,
   nonCriticalExtension [1] HandoverPreparationInformation-v10j0-IEs OPTIONAL
}

AS-Config-v9e0 ::= SEQUENCE {
   sourceDl-CarrierFreq-v9e0 [0] ARFCN-ValueEUTRA-v9e0
}

AS-Context-v1130 ::= SEQUENCE {
   idc-Indication-r11 [0] OCTET STRING (CONTAINING InDeviceCoexIndication-r11)
       OPTIONAL, -- Cond HO2
   mbmsInterestIndication-r11 [1] OCTET STRING (CONTAINING 
      MBMSInterestIndication-r11) OPTIONAL, -- Cond HO2
   ueAssistanceInformation-r11 [2] OCTET STRING (CONTAINING 
      UEAssistanceInformation-r11) OPTIONAL,
   ...,
   [[
      sidelinkUEInformation-r12 [3] OCTET STRING (CONTAINING 
         SidelinkUEInformation-r12) OPTIONAL
   ]],
   [[
      sourceContextEN-DC-r15 [4] OCTET STRING OPTIONAL
   ]],
   [[
      selectedbandCombinationInfoEN-DC-v1540 [5] OCTET STRING OPTIONAL
   ]]
}

AS-Config-v1250 ::= SEQUENCE {
   sourceWlan-OffloadConfig-r12 [0] WLAN-OffloadConfig-r12 OPTIONAL,
   sourceSL-CommConfig-r12 [1] SL-CommConfig-r12 OPTIONAL,
   sourceSL-DiscConfig-r12 [2] SL-DiscConfig-r12 OPTIONAL
}

AS-Config-v1320 ::= SEQUENCE {
   sourceSCellConfigList-r13 [0] SCellToAddModListExt-r13 OPTIONAL,
   sourceRCLWI-Configuration-r13 [1] EXPLICIT RCLWI-Configuration-r13 OPTIONAL
}

AS-Context-v1320 ::= SEQUENCE {
   wlanConnectionStatusReport-r13 [0] OCTET STRING (CONTAINING 
      WLANConnectionStatusReport-r13) OPTIONAL -- Cond HO2
}

AS-Config-v1430 ::= SEQUENCE {
   sourceSL-V2X-CommConfig-r14 [0] SL-V2X-ConfigDedicated-r14 OPTIONAL,
   sourceLWA-Config-r14 [1] LWA-Config-r13 OPTIONAL,
   sourceWLAN-MeasResult-r14 [2] MeasResultListWLAN-r13 OPTIONAL
}

ConfigRestrictInfoDAPS-r16 ::= SEQUENCE {
   maxSCH-TB-BitsDL-r16 [0] INTEGER (1..100) OPTIONAL, -- Cond HO2
   maxSCH-TB-BitsUL-r16 [1] INTEGER (1..100) OPTIONAL -- Cond HO2
}

AS-Context-v1610 ::= SEQUENCE {
   sidelinkUEInformationNR-r16 [0] OCTET STRING OPTIONAL, -- Cond HO3
   ueAssistanceInformationNR-r16 [1] OCTET STRING OPTIONAL, -- Cond HO3
   configRestrictInfoDAPS-r16 [2] ConfigRestrictInfoDAPS-r16 OPTIONAL -- Cond HO2
}

AS-Context-v1620 ::= SEQUENCE {
   ueAssistanceInformationNR-SCG-r16 [0] OCTET STRING OPTIONAL -- Cond HO2
}

ConfigRestrictInfoDAPS-v1630 ::= SEQUENCE {
   daps-PowerCoordinationInfo-r16 [0] DAPS-PowerCoordinationInfo-r16 OPTIONAL -- Cond HO2
}

AS-Context-v1630 ::= SEQUENCE {
   configRestrictInfoDAPS-v1630 [0] ConfigRestrictInfoDAPS-v1630 OPTIONAL -- Cond HO2
}

AS-Config-v1700 ::= SEQUENCE {
   scg-State-r17 [0] ENUMERATED { deactivated(0) } OPTIONAL
}

HandoverPreparationInformation-v1700-IEs ::= SEQUENCE {
   as-Config-v1700 [0] AS-Config-v1700 OPTIONAL, --Cond HO5
   nonCriticalExtension [1] SEQUENCE {

   } OPTIONAL
}

HandoverPreparationInformation-v1630-IEs ::= SEQUENCE {
   as-Context-v1630 [0] AS-Context-v1630 OPTIONAL, --Cond HO2
   nonCriticalExtension [1] HandoverPreparationInformation-v1700-IEs OPTIONAL
}

HandoverPreparationInformation-v1620-IEs ::= SEQUENCE {
   as-Context-v1620 [0] AS-Context-v1620 OPTIONAL, --Cond HO2
   nonCriticalExtension [1] HandoverPreparationInformation-v1630-IEs OPTIONAL
}

HandoverPreparationInformation-v1610-IEs ::= SEQUENCE {
   as-Context-v1610 [0] AS-Context-v1610 OPTIONAL, --Cond HO5
   nonCriticalExtension [1] HandoverPreparationInformation-v1620-IEs OPTIONAL
}

HandoverPreparationInformation-v1540-IEs ::= SEQUENCE {
   sourceRB-ConfigIntra5GC-r15 [0] OCTET STRING OPTIONAL, --Cond HO4
   nonCriticalExtension [1] HandoverPreparationInformation-v1610-IEs OPTIONAL
}

HandoverPreparationInformation-v1530-IEs ::= SEQUENCE {
   ran-NotificationAreaInfo-r15 [0] EXPLICIT RAN-NotificationAreaInfo-r15
       OPTIONAL,
   nonCriticalExtension [1] HandoverPreparationInformation-v1540-IEs OPTIONAL
}

HandoverPreparationInformation-v1430-IEs ::= SEQUENCE {
   as-Config-v1430 [0] AS-Config-v1430 OPTIONAL, -- Cond HO2
   makeBeforeBreakReq-r14 [1] ENUMERATED { true(0) } OPTIONAL, -- Cond HO2
   nonCriticalExtension [2] HandoverPreparationInformation-v1530-IEs OPTIONAL
}

HandoverPreparationInformation-v1320-IEs ::= SEQUENCE {
   as-Config-v1320 [0] AS-Config-v1320 OPTIONAL, -- Cond HO2
   as-Context-v1320 [1] AS-Context-v1320 OPTIONAL, -- Cond HO2
   nonCriticalExtension [2] HandoverPreparationInformation-v1430-IEs OPTIONAL
}

HandoverPreparationInformation-v1250-IEs ::= SEQUENCE {
   ue-SupportedEARFCN-r12 [0] ARFCN-ValueEUTRA-r9 OPTIONAL, -- Cond HO3
   as-Config-v1250 [1] AS-Config-v1250 OPTIONAL, -- Cond HO2
   nonCriticalExtension [2] HandoverPreparationInformation-v1320-IEs OPTIONAL
}

HandoverPreparationInformation-v1130-IEs ::= SEQUENCE {
   as-Context-v1130 [0] AS-Context-v1130 OPTIONAL, -- Cond HO2
   nonCriticalExtension [1] HandoverPreparationInformation-v1250-IEs OPTIONAL
}

-- Regular non-critical extensions:
HandoverPreparationInformation-v9e0-IEs ::= SEQUENCE {
   as-Config-v9e0 [0] AS-Config-v9e0 OPTIONAL, -- Cond HO2
   nonCriticalExtension [1] HandoverPreparationInformation-v1130-IEs OPTIONAL
}

HandoverPreparationInformation-v9d0-IEs ::= SEQUENCE {
   lateNonCriticalExtension [0] OCTET STRING (CONTAINING 
      HandoverPreparationInformation-v9j0-IEs) OPTIONAL,
   nonCriticalExtension [1] HandoverPreparationInformation-v9e0-IEs OPTIONAL
}

HandoverPreparationInformation-v920-IEs ::= SEQUENCE {
   ue-ConfigRelease-r9 [0] ENUMERATED { rel9(0), rel10(1), rel11(2), rel12(3), 
      v10j0(4), v11e0(5), v1280(6), rel13(7), ..., rel14(8), rel15(9), 
      rel16(10), rel17(11) } OPTIONAL, -- Cond HO2
   nonCriticalExtension [1] HandoverPreparationInformation-v9d0-IEs OPTIONAL
}

HandoverPreparationInformation-r8-IEs ::= SEQUENCE {
   ue-RadioAccessCapabilityInfo [0] UE-CapabilityRAT-ContainerList,
   as-Config [1] AS-Config OPTIONAL, -- Cond HO
   rrm-Config [2] RRM-Config OPTIONAL,
   as-Context [3] AS-Context OPTIONAL, -- Cond HO
   nonCriticalExtension [4] HandoverPreparationInformation-v920-IEs OPTIONAL
}

HandoverPreparationInformation ::= SEQUENCE {
   criticalExtensions [0] EXPLICIT CHOICE {
      c1 [0] EXPLICIT CHOICE {
         handoverPreparationInformation-r8 [0] 
            HandoverPreparationInformation-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

SCG-ConfigRestrictInfo-r12 ::= SEQUENCE {
   maxSCH-TB-BitsDL-r12 [0] INTEGER (1..100),
   maxSCH-TB-BitsUL-r12 [1] INTEGER (1..100)
}

MeasResultServCellSCG-r12 ::= SEQUENCE {
   servCellId-r12 [0] ServCellIndex-r10,
   measResultSCell-r12 [1] SEQUENCE {
      rsrpResultSCell-r12 [0] RSRP-Range,
      rsrqResultSCell-r12 [1] RSRQ-Range
   },
   ...,
   [[
      servCellId-r13 [2] ServCellIndex-r13 OPTIONAL,
      measResultSCell-v1310 [3] SEQUENCE {
         rs-sinr-ResultSCell-r13 [0] RS-SINR-Range-r13
      } OPTIONAL
   ]]
}

MeasResultServCellListSCG-r12 ::= SEQUENCE (SIZE (1..maxServCell-r10)) OF 
   MeasResultServCellSCG-r12

DRB-InfoSCG-r12 ::= SEQUENCE {
   eps-BearerIdentity-r12 [0] INTEGER (0..15) OPTIONAL, -- Cond DRB-Setup
   drb-Identity-r12 [1] DRB-Identity,
   drb-Type-r12 [2] ENUMERATED { split(0), scg(1) } OPTIONAL,
   ...
}

DRB-InfoListSCG-r12 ::= SEQUENCE (SIZE (1..maxDRB)) OF DRB-InfoSCG-r12

Cell-ToAddMod-r12 ::= SEQUENCE {
   sCellIndex-r12 [0] SCellIndex-r10,
   cellIdentification-r12 [1] SEQUENCE {
      physCellId-r12 [0] PhysCellId,
      dl-CarrierFreq-r12 [1] ARFCN-ValueEUTRA-r9
   } OPTIONAL, -- Cond SCellAdd
   measResultCellToAdd-r12 [2] SEQUENCE {
      rsrpResult-r12 [0] RSRP-Range,
      rsrqResult-r12 [1] RSRQ-Range
   } OPTIONAL,
   ...,
   [[
      sCellIndex-r13 [3] SCellIndex-r13 OPTIONAL,
      measResultCellToAdd-v1310 [4] SEQUENCE {
         rs-sinr-Result-r13 [0] RS-SINR-Range-r13
      } OPTIONAL
   ]]
}

SCellToAddModListSCG-r12 ::= SEQUENCE (SIZE (1..maxSCell-r10)) OF Cell-ToAddMod-r12

MeasResultServCellListSCG-Ext-r13 ::= SEQUENCE (SIZE (1..maxServCell-r13)) OF 
   MeasResultServCellSCG-r12

SCellToAddModListSCG-Ext-r13 ::= SEQUENCE (SIZE (1..maxSCell-r13)) OF Cell-ToAddMod-r12

MeasResultRSSI-SCG-r13 ::= SEQUENCE {
   servCellId-r13 [0] ServCellIndex-r13,
   measResultForRSSI-r13 [1] MeasResultForRSSI-r13
}

MeasResultListRSSI-SCG-r13 ::= SEQUENCE (SIZE (1..maxServCell-r13)) OF MeasResultRSSI-SCG-r13

DRB-InfoListSCG-r15 ::= SEQUENCE (SIZE (1..maxDRB-r15)) OF DRB-InfoSCG-r12

SCG-ConfigInfo-v1530-IEs ::= SEQUENCE {
   drb-ToAddModListSCG-r15 [0] DRB-InfoListSCG-r15 OPTIONAL,
   drb-ToReleaseListSCG-r15 [1] DRB-ToReleaseList-r15 OPTIONAL,
   nonCriticalExtension [2] SEQUENCE {

   } OPTIONAL
}

SCG-ConfigInfo-v1430-IEs ::= SEQUENCE {
   makeBeforeBreakSCG-Req-r14 [0] ENUMERATED { true(0) } OPTIONAL,
   measGapConfigPerCC-List [1] EXPLICIT MeasGapConfigPerCC-List-r14 OPTIONAL,
   nonCriticalExtension [2] SCG-ConfigInfo-v1530-IEs OPTIONAL
}

SCG-ConfigInfo-v1330-IEs ::= SEQUENCE {
   measResultListRSSI-SCG-r13 [0] MeasResultListRSSI-SCG-r13 OPTIONAL,
   nonCriticalExtension [1] SCG-ConfigInfo-v1430-IEs OPTIONAL
}

SCG-ConfigInfo-v1310-IEs ::= SEQUENCE {
   measResultSSTD-r13 [0] MeasResultSSTD-r13 OPTIONAL,
   sCellToAddModListMCG-Ext-r13 [1] SCellToAddModListExt-r13 OPTIONAL,
   measResultServCellListSCG-Ext-r13 [2] MeasResultServCellListSCG-Ext-r13
       OPTIONAL,
   sCellToAddModListSCG-Ext-r13 [3] SCellToAddModListSCG-Ext-r13 OPTIONAL,
   sCellToReleaseListSCG-Ext-r13 [4] SCellToReleaseListExt-r13 OPTIONAL,
   nonCriticalExtension [5] SCG-ConfigInfo-v1330-IEs OPTIONAL
}

SCG-ConfigInfo-r12-IEs ::= SEQUENCE {
   radioResourceConfigDedMCG-r12 [0] RadioResourceConfigDedicated OPTIONAL,
   sCellToAddModListMCG-r12 [1] SCellToAddModList-r10 OPTIONAL,
   measGapConfig-r12 [2] EXPLICIT MeasGapConfig OPTIONAL,
   powerCoordinationInfo-r12 [3] PowerCoordinationInfo-r12 OPTIONAL,
   scg-RadioConfig-r12 [4] SCG-ConfigPartSCG-r12 OPTIONAL,
   eutra-CapabilityInfo-r12 [5] OCTET STRING (CONTAINING 
      UECapabilityInformation) OPTIONAL,
   scg-ConfigRestrictInfo-r12 [6] SCG-ConfigRestrictInfo-r12 OPTIONAL,
   mbmsInterestIndication-r12 [7] OCTET STRING (CONTAINING 
      MBMSInterestIndication-r11) OPTIONAL,
   measResultServCellListSCG-r12 [8] MeasResultServCellListSCG-r12 OPTIONAL,
   drb-ToAddModListSCG-r12 [9] DRB-InfoListSCG-r12 OPTIONAL,
   drb-ToReleaseListSCG-r12 [10] DRB-ToReleaseList OPTIONAL,
   sCellToAddModListSCG-r12 [11] SCellToAddModListSCG-r12 OPTIONAL,
   sCellToReleaseListSCG-r12 [12] SCellToReleaseList-r10 OPTIONAL,
   p-Max-r12 [13] P-Max OPTIONAL,
   nonCriticalExtension [14] SCG-ConfigInfo-v1310-IEs OPTIONAL
}

SCG-ConfigInfo-r12 ::= SEQUENCE {
   criticalExtensions [0] EXPLICIT CHOICE {
      c1 [0] EXPLICIT CHOICE {
         scg-ConfigInfo-r12 [0] SCG-ConfigInfo-r12-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

UEPagingCoverageInformation-r13-IEs ::= SEQUENCE {
   mpdcch-NumRepetition-r13 [0] INTEGER (1..256) OPTIONAL,
   nonCriticalExtension [1] SEQUENCE {

   } OPTIONAL
}

UEPagingCoverageInformation ::= SEQUENCE {
   criticalExtensions [0] EXPLICIT CHOICE {
      c1 [0] EXPLICIT CHOICE {
         uePagingCoverageInformation-r13 [0] 
            UEPagingCoverageInformation-r13-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

UERadioAccessCapabilityInformation-r8-IEs ::= SEQUENCE {
   ue-RadioAccessCapabilityInfo [0] OCTET STRING (CONTAINING 
      UECapabilityInformation),
   nonCriticalExtension [1] SEQUENCE {

   } OPTIONAL
}

UERadioAccessCapabilityInformation ::= SEQUENCE {
   criticalExtensions [0] EXPLICIT CHOICE {
      c1 [0] EXPLICIT CHOICE {
         ueRadioAccessCapabilityInformation-r8 [0] 
            UERadioAccessCapabilityInformation-r8-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

UERadioPagingInformation-v1610-IEs ::= SEQUENCE {
   accessStratumRelease-r16 [0] ENUMERATED { true(0) } OPTIONAL,
   nonCriticalExtension [1] SEQUENCE {

   } OPTIONAL
}

UERadioPagingInformation-v1310-IEs ::= SEQUENCE {
   supportedBandListEUTRAForPaging-r13 [0] SEQUENCE (SIZE (1..maxBands)) OF 
      FreqBandIndicator-r11 OPTIONAL,
   nonCriticalExtension [1] UERadioPagingInformation-v1610-IEs OPTIONAL
}

UERadioPagingInformation-r12-IEs ::= SEQUENCE {
   ue-RadioPagingInfo-r12 [0] OCTET STRING (CONTAINING UE-RadioPagingInfo-r12),
   nonCriticalExtension [1] UERadioPagingInformation-v1310-IEs OPTIONAL
}

UERadioPagingInformation ::= SEQUENCE {
   criticalExtensions [0] EXPLICIT CHOICE {
      c1 [0] EXPLICIT CHOICE {
         ueRadioPagingInformation-r12 [0] UERadioPagingInformation-r12-IEs,
         spare7 [1] NULL,
         spare6 [2] NULL,
         spare5 [3] NULL,
         spare4 [4] NULL,
         spare3 [5] NULL,
         spare2 [6] NULL,
         spare1 [7] NULL
      },
      criticalExtensionsFuture [1] SEQUENCE {

      }
   }
}

-- Value assignments

maxReestabInfo INTEGER ::= 32


END
