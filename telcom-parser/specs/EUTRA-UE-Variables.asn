-- This file was generated by the Objective Systems ASN1C Compiler
-- (http://www.obj-sys.com).  Version: 7.7.2, Date: 13-Oct-2023.

EUTRA-UE-Variables DEFINITIONS AUTOMATIC TAGS ::= BEGIN

IMPORTS

AbsoluteTimeInfo-r10, AreaConfiguration-r10, AreaConfiguration-v1130, 
   ARFCN-ValueNR-r15, BT-NameList-r15, CarrierFreqGERAN, CellIdentity, 
   CellList-r15, CondReconfigurationToAddModList-r16, ConnEstFailReport-r11, 
   EUTRA-CarrierList-r15, SpeedStateScaleFactors, C-RNTI, 
   LoggedEventTriggerConfig-r17, LoggingDuration-r10, LoggingInterval-r10, 
   LogMeasInfo-r10, MeasCSI-RS-Id-r12, MeasId, MeasId-v1250, MeasIdToAddModList
   , MeasIdToAddModListExt-r12, MeasIdToAddModList-v1310, 
   MeasIdToAddModListExt-v1310, MeasObjectToAddModList, 
   MeasObjectToAddModList-v9e0, MeasObjectToAddModListExt-r13, 
   MeasResultListExtIdle-r16, MeasResultListIdle-r15, MeasResultListIdleNR-r16
   , MeasScaleFactor-r12, MobilityStateParameters, NeighCellConfig, 
   NR-CarrierList-r16, PhysCellId, PhysCellIdCDMA2000, PhysCellIdGERAN, 
   PhysCellIdUTRA-FDD, PhysCellIdUTRA-TDD, PLMN-Identity, 
   PLMN-IdentityList3-r11, QuantityConfig, ReportConfigToAddModList, 
   RLF-Report-r9, TargetMBSFN-AreaList-r12, TraceReference-r10, 
   Tx-ResourcePoolMeasList-r14, VisitedCellInfoList-r12, maxCellMeas, 
   maxCSI-RS-Meas-r12, maxMeasId, maxMeasId-r12, maxRS-Index-r15, 
   PhysCellIdNR-r15, RS-IndexNR-r15, UL-DelayConfig-r13, ValidityAreaList-r16, 
   WLAN-CarrierInfo-r13, WLAN-Identifiers-r12, WLAN-Id-List-r13, 
   WLAN-NameList-r15, WLAN-Status-r13, WLAN-Status-v1430, 
   WLAN-SuspendConfig-r14
FROM EUTRA-RRC-Definitions ;

-- Productions

VarMobilityHistoryReport-r12 ::= VisitedCellInfoList-r12

VarConditionalReconfiguration ::= SEQUENCE {
-- Conditional reconfigurations list
   condReconfigurationList-r16 [0] CondReconfigurationToAddModList-r16 OPTIONAL
}

VarConnEstFailReport-r11 ::= SEQUENCE {
   connEstFailReport-r11 [0] ConnEstFailReport-r11,
   plmn-Identity-r11 [1] PLMN-Identity
}

VarLogMeasConfig-r10 ::= SEQUENCE {
   areaConfiguration-r10 [0] EXPLICIT AreaConfiguration-r10 OPTIONAL,
   loggingDuration-r10 [1] LoggingDuration-r10,
   loggingInterval-r10 [2] LoggingInterval-r10
}

VarLogMeasConfig-r11 ::= SEQUENCE {
   areaConfiguration-r10 [0] EXPLICIT AreaConfiguration-r10 OPTIONAL,
   areaConfiguration-v1130 [1] AreaConfiguration-v1130 OPTIONAL,
   loggingDuration-r10 [2] LoggingDuration-r10,
   loggingInterval-r10 [3] LoggingInterval-r10
}

VarLogMeasConfig-r12 ::= SEQUENCE {
   areaConfiguration-r10 [0] EXPLICIT AreaConfiguration-r10 OPTIONAL,
   areaConfiguration-v1130 [1] AreaConfiguration-v1130 OPTIONAL,
   loggingDuration-r10 [2] LoggingDuration-r10,
   loggingInterval-r10 [3] LoggingInterval-r10,
   targetMBSFN-AreaList-r12 [4] TargetMBSFN-AreaList-r12 OPTIONAL
}

VarLogMeasConfig-r15 ::= SEQUENCE {
   areaConfiguration-r10 [0] EXPLICIT AreaConfiguration-r10 OPTIONAL,
   areaConfiguration-v1130 [1] AreaConfiguration-v1130 OPTIONAL,
   loggingDuration-r10 [2] LoggingDuration-r10,
   loggingInterval-r10 [3] LoggingInterval-r10,
   targetMBSFN-AreaList-r12 [4] TargetMBSFN-AreaList-r12 OPTIONAL,
   bt-NameList-r15 [5] BT-NameList-r15 OPTIONAL,
   wlan-NameList-r15 [6] WLAN-NameList-r15 OPTIONAL
}

VarLogMeasConfig-r17 ::= SEQUENCE {
   areaConfiguration-r10 [0] EXPLICIT AreaConfiguration-r10 OPTIONAL,
   areaConfiguration-v1130 [1] AreaConfiguration-v1130 OPTIONAL,
   loggingDuration-r10 [2] LoggingDuration-r10,
   loggingInterval-r10 [3] LoggingInterval-r10,
   targetMBSFN-AreaList-r12 [4] TargetMBSFN-AreaList-r12 OPTIONAL,
   bt-NameList-r15 [5] BT-NameList-r15 OPTIONAL,
   wlan-NameList-r15 [6] WLAN-NameList-r15 OPTIONAL,
   loggedEventTriggerConfig-r17 [7] LoggedEventTriggerConfig-r17 OPTIONAL,
   measUncomBarPre-r17 [8] ENUMERATED { true(0) } OPTIONAL
}

LogMeasInfoList2-r10 ::= SEQUENCE (SIZE (1..maxLogMeas-r10)) OF LogMeasInfo-r10

VarLogMeasReport-r10 ::= SEQUENCE {
   traceReference-r10 [0] TraceReference-r10,
   traceRecordingSessionRef-r10 [1] OCTET STRING (SIZE (2)),
   tce-Id-r10 [2] OCTET STRING (SIZE (1)),
   plmn-Identity-r10 [3] PLMN-Identity,
   absoluteTimeInfo-r10 [4] AbsoluteTimeInfo-r10,
   logMeasInfoList-r10 [5] LogMeasInfoList2-r10
}

VarLogMeasReport-r11 ::= SEQUENCE {
   traceReference-r10 [0] TraceReference-r10,
   traceRecordingSessionRef-r10 [1] OCTET STRING (SIZE (2)),
   tce-Id-r10 [2] OCTET STRING (SIZE (1)),
   plmn-IdentityList-r11 [3] PLMN-IdentityList3-r11,
   absoluteTimeInfo-r10 [4] AbsoluteTimeInfo-r10,
   logMeasInfoList-r10 [5] LogMeasInfoList2-r10
}

VarMeasConfig ::= SEQUENCE {
--Measurement identities
   measIdList [0] MeasIdToAddModList OPTIONAL,
   measIdListExt-r12 [1] MeasIdToAddModListExt-r12 OPTIONAL,
   measIdList-v1310 [2] MeasIdToAddModList-v1310 OPTIONAL,
   measIdListExt-v1310 [3] MeasIdToAddModListExt-v1310 OPTIONAL,
--Measurement objects
   measObjectList [4] MeasObjectToAddModList OPTIONAL,
   measObjectListExt-r13 [5] MeasObjectToAddModListExt-r13 OPTIONAL,
   measObjectList-v9i0 [6] MeasObjectToAddModList-v9e0 OPTIONAL,
--Reporting configurations
   reportConfigList [7] ReportConfigToAddModList OPTIONAL,
--Other parameters
   quantityConfig [8] QuantityConfig OPTIONAL,
   measScaleFactor-r12 [9] MeasScaleFactor-r12 OPTIONAL,
   s-Measure [10] INTEGER (-140..-44) OPTIONAL,
   speedStatePars [11] EXPLICIT CHOICE {
      release [0] NULL,
      setup [1] SEQUENCE {
         mobilityStateParameters [0] MobilityStateParameters,
         timeToTrigger-SF [1] SpeedStateScaleFactors
      }
   } OPTIONAL,
   allowInterruptions-r11 [12] BOOLEAN OPTIONAL
}

VarMeasIdleConfig-r15 ::= SEQUENCE {
   measIdleCarrierListEUTRA-r15 [0] EUTRA-CarrierList-r15 OPTIONAL,
   measIdleDuration-r15 [1] ENUMERATED { sec10(0), sec30(1), sec60(2), 
      sec120(3), sec180(4), sec240(5), sec300(6) }
}

VarMeasIdleConfig-r16 ::= SEQUENCE {
   measIdleCarrierListNR-r16 [0] NR-CarrierList-r16 OPTIONAL,
   validityAreaList-r16 [1] ValidityAreaList-r16 OPTIONAL
}

VarMeasIdleReport-r15 ::= SEQUENCE {
   measReportIdle-r15 [0] MeasResultListIdle-r15
}

VarMeasIdleReport-r16 ::= SEQUENCE {
   measReportIdle-r16 [0] MeasResultListExtIdle-r16 OPTIONAL,
   measReportIdleNR-r16 [1] MeasResultListIdleNR-r16 OPTIONAL
}

SSB-IndexList-r15 ::= SEQUENCE (SIZE (1..maxRS-Index-r15)) OF RS-IndexNR-r15

CellsTriggeredList ::= SEQUENCE (SIZE (1..maxCellMeas)) OF CHOICE {
   physCellIdEUTRA [0] PhysCellId,
   physCellIdUTRA [1] EXPLICIT CHOICE {
      fdd [0] PhysCellIdUTRA-FDD,
      tdd [1] PhysCellIdUTRA-TDD
   },
   physCellIdGERAN [2] SEQUENCE {
      carrierFreq [0] CarrierFreqGERAN,
      physCellId [1] PhysCellIdGERAN
   },
   physCellIdCDMA2000 [3] PhysCellIdCDMA2000,
   wlan-Identifiers-r13 [4] WLAN-Identifiers-r12,
   physCellIdNR-r15 [5] SEQUENCE {
      carrierFreq [0] ARFCN-ValueNR-r15,
      physCellId [1] PhysCellIdNR-r15,
      rs-IndexList-r15 [2] SSB-IndexList-r15 OPTIONAL
   }
}

CSI-RS-TriggeredList-r12 ::= SEQUENCE (SIZE (1..maxCSI-RS-Meas-r12)) OF MeasCSI-RS-Id-r12

VarMeasReport ::= SEQUENCE {
--List of measurement that have been triggered
   measId [0] MeasId,
   measId-v1250 [1] MeasId-v1250 OPTIONAL,
   cellsTriggeredList [2] CellsTriggeredList OPTIONAL,
   csi-RS-TriggeredList-r12 [3] CSI-RS-TriggeredList-r12 OPTIONAL,
   poolsTriggeredList-r14 [4] Tx-ResourcePoolMeasList-r14 OPTIONAL,
   numberOfReportsSent [5] INTEGER
}

VarMeasReportList ::= SEQUENCE (SIZE (1..maxMeasId)) OF VarMeasReport

VarMeasReportList-r12 ::= SEQUENCE (SIZE (1..maxMeasId-r12)) OF VarMeasReport

VarPendingRnaUpdate-r15 ::= SEQUENCE {
   pendingRnaUpdate [0] BOOLEAN OPTIONAL
}

VarRLF-Report-r10 ::= SEQUENCE {
   rlf-Report-r10 [0] RLF-Report-r9,
   plmn-Identity-r10 [1] PLMN-Identity
}

VarRLF-Report-r11 ::= SEQUENCE {
   rlf-Report-r10 [0] RLF-Report-r9,
   plmn-IdentityList-r11 [1] PLMN-IdentityList3-r11
}

VarShortINACTIVE-MAC-Input-r15 ::= SEQUENCE {
   cellIdentity-r15 [0] CellIdentity,
   physCellId-r15 [1] PhysCellId,
   c-RNTI-r15 [2] C-RNTI
}

VarShortMAC-Input ::= SEQUENCE {
   cellIdentity [0] CellIdentity,
   physCellId [1] PhysCellId,
   c-RNTI [2] C-RNTI
}

VarShortResumeMAC-Input-r13 ::= SEQUENCE {
   cellIdentity-r13 [0] CellIdentity,
   physCellId-r13 [1] PhysCellId,
   c-RNTI-r13 [2] C-RNTI,
   resumeDiscriminator-r13 [3] BIT STRING  (SIZE (1))
}

VarWLAN-MobilityConfig ::= SEQUENCE {
   wlan-MobilitySet-r13 [0] WLAN-Id-List-r13 OPTIONAL,
   successReportRequested [1] ENUMERATED { true(0) } OPTIONAL,
   wlan-SuspendConfig-r14 [2] WLAN-SuspendConfig-r14 OPTIONAL
}

VarWLAN-Status-r13 ::= SEQUENCE {
   status-r13 [0] WLAN-Status-r13,
   status-r14 [1] WLAN-Status-v1430 OPTIONAL
}

-- Value assignments

maxLogMeas-r10 INTEGER ::= 4060


END
